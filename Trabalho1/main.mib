DISCOVERY-MIB DEFINITIONS ::= BEGIN C

-- 1.sudo cp main.mib /usr/share/snmp/mibs/

-- 2. snmptranslate -m +main -Tp

-- 3. snmpwalk -v2c -c public -m +main <endereço_ip_do_dispositivo> objetosMinhaRede

IMPORTS
    MODULE-IDENTITY, OBJECT-TYPE, IpAddress, Counter32, TimeTicks, experimental
        FROM SNMPv2-SMI
    OBJECT-GROUP
        FROM SNMPv2-CONF;

discoveryModule MODULE-IDENTITY
    LAST-UPDATED "202410300000Z"
    ORGANIZATION "Departamento de Computacao Aplicada - UFSM"
    CONTACT-INFO
        "Diogo Rocha
         Centro de Tecnologia - UFSM"
    DESCRIPTION
        "MIB para monitoramento e configuracao de uma ferramenta de autodescoberta."
    ::= { experimental 888 }

discoveryObjects OBJECT IDENTIFIER ::= { discoveryModule 1 }

-- Objetos de informações gerais do sistema

systemStatus OBJECT-TYPE
    SYNTAX      INTEGER { ativo(1), inativo(2) }
    MAX-ACCESS  read-write
    STATUS      current
    DESCRIPTION
        "Status atual da ferramenta de autodescoberta."
    ::= { discoveryObjects 1 }

discoveryInterval OBJECT-TYPE
    SYNTAX      TimeTicks
    MAX-ACCESS  read-write
    STATUS      current
    DESCRIPTION
        "Intervalo de tempo em que a ferramenta realiza a autodescoberta."
    ::= { discoveryObjects 2 }

totalDevicesDiscovered OBJECT-TYPE
    SYNTAX      Counter32
    MAX-ACCESS  read-only
    STATUS      current
    DESCRIPTION
        "Contagem total de dispositivos descobertos pelo sistema."
    ::= { discoveryObjects 3 }

adminContact OBJECT-TYPE
    SYNTAX      OCTET STRING (SIZE (0..255))
    MAX-ACCESS  read-write
    STATUS      current
    DESCRIPTION
        "Informacao de contato do administrador responsavel pela ferramenta de autodescoberta."
    ::= { discoveryObjects 4 }

-- Tabela de informações de dispositivos descobertos

discoveredDevicesTable OBJECT-TYPE
    SYNTAX      SEQUENCE OF DiscoveredDeviceEntry
    MAX-ACCESS  not-accessible
    STATUS      current
    DESCRIPTION
        "Tabela contendo informacoes dos dispositivos descobertos pela ferramenta."
    ::= { discoveryObjects 5 }

discoveredDeviceEntry OBJECT-TYPE
    SYNTAX      DiscoveredDeviceEntry
    MAX-ACCESS  not-accessible
    STATUS      current
    DESCRIPTION
        "Entrada contendo informacoes de cada dispositivo descoberto."
    INDEX       { deviceIp }
    ::= { discoveredDevicesTable 1 }

DiscoveredDeviceEntry ::= SEQUENCE {
    deviceIp                IpAddress,
    deviceName              OCTET STRING,
    deviceStatus            INTEGER,
    deviceUptime            TimeTicks
}

deviceIp OBJECT-TYPE
    SYNTAX      IpAddress
    MAX-ACCESS  not-accessible
    STATUS      current
    DESCRIPTION
        "Endereco IP do dispositivo descoberto."
    ::= { discoveredDeviceEntry 1 }

deviceName OBJECT-TYPE
    SYNTAX      OCTET STRING (SIZE (0..255))
    MAX-ACCESS  read-only
    STATUS      current
    DESCRIPTION
        "Nome do dispositivo descoberto."
    ::= { discoveredDeviceEntry 2 }

deviceStatus OBJECT-TYPE
    SYNTAX      INTEGER { online(1), offline(2) }
    MAX-ACCESS  read-only
    STATUS      current
    DESCRIPTION
        "Status atual do dispositivo descoberto."
    ::= { discoveredDeviceEntry 3 }

deviceUptime OBJECT-TYPE
    SYNTAX      TimeTicks
    MAX-ACCESS  read-only
    STATUS      current
    DESCRIPTION
        "Tempo em que o dispositivo descoberto esta ativo, desde o ultimo reinicio."
    ::= { discoveredDeviceEntry 4 }

-- Grupo de objetos para facilitar a visualização e controle da tabela

discoveryGroup OBJECT-GROUP
    OBJECTS { 
        systemStatus,
        discoveryInterval,
        totalDevicesDiscovered,
        adminContact,
        deviceName,
        deviceStatus,
        deviceUptime
    }
    STATUS      current
    DESCRIPTION
        "Grupo de objetos para a ferramenta de autodescoberta."
    ::= { discoveryModule 2 }

END
